FME workspace postgis2esri.fmw

Parameters:
- FORMATS_LIST = shp   # Formats list
- DestDataset_ESRISHAPE = /Users/nisrinedrissi/Downloads   # Destination Esri Shapefile Folder
- DestDataset_ACAD = /Users/nisrinedrissi/Downloads   # Destination Autodesk AutoCAD DWG/DXF File
- SourceDataset_POSTGIS = routes_donnees   # Connection

Readers:
- POSTGIS_1: POSTGIS from $(SourceDataset_POSTGIS)

Writers:
- ESRISHAPE_1: ESRISHAPE to $(DestDataset_ESRISHAPE)
- ACAD_1: ACAD to $(DestDataset_ACAD)

routes.surface_route (reader POSTGIS_1)
    attributes: source_géométrique varchar(27), nature varchar(18), z_moyen numeric(9,1), id char(200)
    -> Tester_SHP
    -> Tester_DXF
Tester_SHP
    TEST_MODE = Automatic
    TEST_DESCRIPTION = ""
    BOOL_OP = OR
    TEST_CLAUSE = TEST $(FORMATS_LIST) CONTAINS SHP
    PASSED -> Shapefile1 (writer ESRISHAPE_1)
    PASSED -> Tester_SHP_Passed
Tester_SHP_Passed: Inspector
Shapefile1 (writer ESRISHAPE_1)
Tester_DXF
    TEST_MODE = Automatic
    TEST_DESCRIPTION = ""
    BOOL_OP = OR
    TEST_CLAUSE = TEST $(FORMATS_LIST) CONTAINS DXF
    PASSED -> Tester_SHP_Passed_2
    PASSED -> Layer1 (writer ACAD_1)
Tester_SHP_Passed_2: Inspector
Layer1 (writer ACAD_1)
