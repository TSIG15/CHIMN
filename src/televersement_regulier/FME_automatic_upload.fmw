FME workspace FME_automatic_upload.fmw

Parameters:
- POSTGIS_TABLE = hydrographie.surface_eau
- DEST = /Users/nisrinedrissi/Downloads
- FORMATS_LIST = shp dxf gml kml jpeg png geotiff
- SRS_LIST = 2154 32631 3857 4326   # Liste SRS
- LOG = /Users/nisrinedrissi/Downloads/log
- SourceDataset_POSTGIS = exempleDonnee   # Connection
- destFiles = $(DEST)   # Destination generale
- DestKML = $(destFiles)/exports/kml   # Destination KML
- DestSHP = /Users/nisrinedrissi/Downloads/exports/shp   # Destination SHP
- DestDXF2154 = $(destFiles)/exports/dxf/EPSG-2154/$(POSTGIS_TABLE).zip   # Destination DXF 2154
- DestDXF32631 = $(destFiles)/exports/dxf/EPSG-32631/$(POSTGIS_TABLE).zip   # Destination DXF 32631
- DestDXF3857 = $(destFiles)/exports/dxf/EPSG-3857/$(POSTGIS_TABLE).zip   # Destination DXF 3857
- DestDXF4326 = /Users/nisrinedrissi/Downloads/exports/dxf/EPSG-4326/$(POSTGIS_TABLE).zip   # Destination DXF 4326
- DestGML2154 = /Users/nisrinedrissi/Downloads/exports/gml/EPSG-2154/hydrographie.surface_eau.zip   # Destination GML
- DestGML32631 = $(destFiles)/exports/gml/EPSG-32631/$(POSTGIS_TABLE).zip   # Destination GML 32631
- DestGML3857 = $(destFiles)/exports/gml/EPSG-3857/$(POSTGIS_TABLE).zip   # Destination GML 3857
- DestGML4326 = /Users/nisrinedrissi/Downloads/exports/gml/EPSG-4326/hydrographie.surface_eau.zip   # Destination GML 4326
- DestJPEG32631 = /Users/nisrinedrissi/Downloads/exports/jpeg/EPSG-32631   # Destination JPEG 32631
- DestJPEG2154 = /Users/nisrinedrissi/Downloads/exports/jpeg/EPSG-2154   # Destination JPEG
- DestJPEG3857 = /Users/nisrinedrissi/Downloads/exports/jpeg/EPSG-3857   # Destination JPEG 3857
- DestJPEG4326 = $(destFiles)/exports/jpeg/EPSG-4326   # Destination JEP 4326
- DestPNG2154 = /Users/nisrinedrissi/Downloads/exports/png/EPSG-2154   # Destination PNG 2154
- DestPNG32631 = $(destFiles)/exports/png/EPSG-32631   # Destination PNG 32631
- DestPNG3857 = $(destFiles)/exports/png/EPSG-3857   # Destination PNG 3857
- DestPNG4326 = $(destFiles)/exports/png/EPSG-4326   # Destination PNG 4326
- DestGEOTIFF2154 = /Users/nisrinedrissi/Downloads/exports/geotiff/EPSG-2154   # Destination GEOTIFF 2154
- DestGEOTIFF32631 = $(destFiles)/exports/geotiff/EPSG-32631   # Destination GEOTIFF 32631
- DestGEOTIFF3857 = $(destFiles)/exports/geotiff/EPSG-3857   # Destination GEOTIFF 3857
- DestGEOTIFF4326 = $(destFiles)/exports/geotiff/EPSG-4326   # Destination GEOTIFF 4326

Readers:
- POSTGIS_1: POSTGIS from $(SourceDataset_POSTGIS)

Writers:
- ESRISHAPE_1: ESRISHAPE to $(DestSHP)
- ACAD_4: ACAD to $(DestDXF2154)
- ACAD_3: ACAD to $(DestDXF32631)
- ACAD_1: ACAD to $(DestDXF3857)
- ACAD_2: ACAD to $(DestDXF4326)
- OGCKML_1: OGCKML to $(DestKML)
- GML_1: GML to $(DestGML2154)
- GML_4: GML to $(DestGML32631)
- GML_3: GML to $(DestGML3857)
- GML_2: GML to $(DestGML4326)
- GEOTIFF_1: GEOTIFF to $(DestGEOTIFF2154)
- GEOTIFF_2: GEOTIFF to $(DestGEOTIFF32631)
- GEOTIFF_3: GEOTIFF to $(DestGEOTIFF3857)
- GEOTIFF_4: GEOTIFF to $(DestGEOTIFF4326)
- JPEG_1: JPEG to $(DestJPEG2154)
- JPEG_2: JPEG to $(DestJPEG32631)
- JPEG_3: JPEG to $(DestJPEG3857)
- JPEG_4: JPEG to $(DestJPEG4326)
- PNGRASTER_1: PNGRASTER to $(DestPNG2154)
- PNGRASTER_2: PNGRASTER to $(DestPNG32631)
- PNGRASTER_3: PNGRASTER to $(DestPNG3857)
- PNGRASTER_4: PNGRASTER to $(DestPNG4326)

hydrographie.surface_eau (reader POSTGIS_1)
    attributes: source_geo varchar(27), nature varchar(13), régime_eaux varchar(12), z_min numeric(9,1), z_max numeric(9,1), id char(200)
    -> Multiple_Test_Reprojector [input 1]
    -> Multiple_Test_Reprojector [input 2]
    -> Multiple_Test_Reprojector [input 3]
    -> Multiple_Test_Reprojector [input 4]
Multiple_Test_Reprojector
    DEST = C:\Users\ndrissi\Downloads
    SRS_LIST = $(SRS_LIST)
    Reprojector_3857_Reprojected -> CoordinateSystemExtractor
    Reprojector_32631_Reprojected -> CoordinateSystemExtractor
    Reprojector_2154_Reprojected -> CoordinateSystemExtractor
    Reprojector_3857_Reprojected_2 -> CoordinateSystemExtractor
Note: extractio de la SRS
CoordinateSystemExtractor
    CRDSYS_ATTR = _coordsys
    -> StringReplacer
StringReplacer
    SRC_ATTRS = _coordsys
    REPLACE_TEXT = -
    REGEXP = no
    NO_MATCH = _FME_NO_OP_
    FIND_TEXT = :
    CASE = no
    -> StringReplacer_2
StringReplacer_2
    SRC_ATTRS = _coordsys
    REPLACE_TEXT = -
    REGEXP = no
    NO_MATCH = _FME_NO_OP_
    FIND_TEXT = .
    CASE = no
    -> AttributeCreator_2
AttributeCreator_2
    ATTR_LIST = data_name,$(POSTGIS_TABLE),fanout_attribute,@Value(_coordsys)\$(POSTGIS_TABLE)
    -> Tester_shp
    -> Tester_kml
    -> Tester_dxf
    -> Tester_gml
    -> Tester_geotiff
    -> Tester_png
    -> Tester_jpeg
Tester_shp
    TEST_CLAUSE = TEST $(FORMATS_LIST) CONTAINS shp
    TEST_DESCRIPTION = Test si parametre format contient shp
    BOOL_OP = OR
    TEST_MODE = Automatic
    PASSED -> Multiple_Test_Reprojection_SHP [input 3]
    PASSED -> Multiple_Test_Reprojection_SHP [input 1]
    PASSED -> Multiple_Test_Reprojection_SHP [input 2]
    PASSED -> Multiple_Test_Reprojection_SHP [input 4]
Multiple_Test_Reprojection_SHP
    DEST = C:\Users\ndrissi\Downloads
    _COORDSYS = @Value(_coordsys)
    dest = exports
    Tester_shp_EPSG:32631_2_Passed -> 215400 (writer ESRISHAPE_1)
    Tester_shp_EPSG:3857_2_Passed -> 21540000 (writer ESRISHAPE_1)
    Tester_EPSG:2154_2_Passed -> 21540001 (writer ESRISHAPE_1)
    Tester_shp_EPSG:3857_2_Passed_2 -> 2154000000 (writer ESRISHAPE_1)
21540001 (writer ESRISHAPE_1)
    attributes: Id number(15,0), EDGE_ID number(15,0), DATASET_ID long, FROM_ID number(15,0), FROM_ID_BR short, TO_ID number(15,0), TO_ID_BR short, DTRF char(2), LENIENT_ON char(2), FRC short, FOW short, SLIPRD short, BUA_FLAG short, TIF_DSET char(3), METERS number(15,1), SPEEDMAX short, SPEEDCAT short, UC_DIR char(4), BRU_LINE short, BRU_AREA short, MN_RC short, GROUNDLEVE short, GROUNDLEV1 short, LEFTNAME char(254), RIGHTNAME char(254), New_SN char(100), New_Geo char(50), Comment char(50), Update char(50)
215400 (writer ESRISHAPE_1)
    attributes: Id number(15,0), EDGE_ID number(15,0), DATASET_ID long, FROM_ID number(15,0), FROM_ID_BR short, TO_ID number(15,0), TO_ID_BR short, DTRF char(2), LENIENT_ON char(2), FRC short, FOW short, SLIPRD short, BUA_FLAG short, TIF_DSET char(3), METERS number(15,1), SPEEDMAX short, SPEEDCAT short, UC_DIR char(4), BRU_LINE short, BRU_AREA short, MN_RC short, GROUNDLEVE short, GROUNDLEV1 short, LEFTNAME char(254), RIGHTNAME char(254), New_SN char(100), New_Geo char(50), Comment char(50), Update char(50)
21540000 (writer ESRISHAPE_1)
    attributes: Id number(15,0), EDGE_ID number(15,0), DATASET_ID long, FROM_ID number(15,0), FROM_ID_BR short, TO_ID number(15,0), TO_ID_BR short, DTRF char(2), LENIENT_ON char(2), FRC short, FOW short, SLIPRD short, BUA_FLAG short, TIF_DSET char(3), METERS number(15,1), SPEEDMAX short, SPEEDCAT short, UC_DIR char(4), BRU_LINE short, BRU_AREA short, MN_RC short, GROUNDLEVE short, GROUNDLEV1 short, LEFTNAME char(254), RIGHTNAME char(254), New_SN char(100), New_Geo char(50), Comment char(50), Update char(50)
2154000000 (writer ESRISHAPE_1)
    attributes: Id number(15,0), EDGE_ID number(15,0), DATASET_ID long, FROM_ID number(15,0), FROM_ID_BR short, TO_ID number(15,0), TO_ID_BR short, DTRF char(2), LENIENT_ON char(2), FRC short, FOW short, SLIPRD short, BUA_FLAG short, TIF_DSET char(3), METERS number(15,1), SPEEDMAX short, SPEEDCAT short, UC_DIR char(4), BRU_LINE short, BRU_AREA short, MN_RC short, GROUNDLEVE short, GROUNDLEV1 short, LEFTNAME char(254), RIGHTNAME char(254), New_SN char(100), New_Geo char(50), Comment char(50), Update char(50)
Tester_kml
    TEST_CLAUSE = TEST $(FORMATS_LIST) CONTAINS kml
    TEST_DESCRIPTION = Test si parametre format contient kml
    BOOL_OP = OR
    TEST_MODE = Automatic
    PASSED -> Multiple_Test_Reprojection_KML [input 1]
    PASSED -> Multiple_Test_Reprojection_KML [input 2]
    PASSED -> Multiple_Test_Reprojection_KML [input 3]
    PASSED -> Multiple_Test_Reprojection_KML [input 4]
Multiple_Test_Reprojection_KML
    DEST = C:\Users\ndrissi\Downloads
    _COORDSYS = @Value(_coordsys)
    dest = exports
    Tester_EPSG:2154_2_Passed -> 2154 (writer OGCKML_1)
    Tester_shp_EPSG:32631_2_Passed -> 32631 (writer OGCKML_1)
    Tester_shp_EPSG:3857_2_Passed -> 3857 (writer OGCKML_1)
    Tester_shp_EPSG:3857_2_Passed_2 -> 4326 (writer OGCKML_1)
2154 (writer OGCKML_1)
    attributes: source_geo kml_char(27), nature kml_char(13), régime_eaux kml_char(12), z_min kml_real32, z_max kml_real32, id kml_char(200), _coordsys kml_char(200), data_name kml_char(200), fanout_attribute kml_char(200)
32631 (writer OGCKML_1)
    attributes: source_geo kml_char(27), nature kml_char(13), régime_eaux kml_char(12), z_min kml_real32, z_max kml_real32, id kml_char(200), _coordsys kml_char(200), data_name kml_char(200), fanout_attribute kml_char(200)
3857 (writer OGCKML_1)
    attributes: source_geo kml_char(27), nature kml_char(13), régime_eaux kml_char(12), z_min kml_real32, z_max kml_real32, id kml_char(200), _coordsys kml_char(200), data_name kml_char(200), fanout_attribute kml_char(200)
4326 (writer OGCKML_1)
    attributes: source_geo kml_char(27), nature kml_char(13), régime_eaux kml_char(12), z_min kml_real32, z_max kml_real32, id kml_char(200), _coordsys kml_char(200), data_name kml_char(200), fanout_attribute kml_char(200)
Tester_dxf
    TEST_CLAUSE = TEST $(FORMATS_LIST) CONTAINS dxf
    TEST_DESCRIPTION = Test si parametre format contient dxf
    BOOL_OP = OR
    TEST_MODE = Automatic
    PASSED -> Multiple_Test_Reprojection_DXF [input 1]
    PASSED -> Multiple_Test_Reprojection_DXF [input 2]
    PASSED -> Multiple_Test_Reprojection_DXF [input 3]
    PASSED -> Multiple_Test_Reprojection_DXF [input 4]
Multiple_Test_Reprojection_DXF
    DEST = C:\Users\ndrissi\Downloads
    _COORDSYS = @Value(_coordsys)
    dest = exports
    Tester_shp_EPSG:3857_2_Passed_2 -> hydrographie.surface_eau (writer ACAD_2)
    Tester_shp_EPSG:3857_2_Passed -> hydrographie.surface_eau (writer ACAD_1)
    Tester_shp_EPSG:32631_2_Passed -> hydrographie.surface_eau (writer ACAD_3)
    Tester_EPSG:2154_2_Passed -> hydrographie.surface_eau (writer ACAD_4)
hydrographie.surface_eau (writer ACAD_4)
    attributes: source_geo char(27), nature char(13), régime_eaux char(12), z_min number(9,1), z_max number(9,1), id char(200)
hydrographie.surface_eau (writer ACAD_3)
    attributes: source_geo char(27), nature char(13), régime_eaux char(12), z_min number(9,1), z_max number(9,1), id char(200)
hydrographie.surface_eau (writer ACAD_1)
    attributes: source_geo char(27), nature char(13), régime_eaux char(12), z_min number(9,1), z_max number(9,1), id char(200)
hydrographie.surface_eau (writer ACAD_2)
    attributes: source_geo char(27), nature char(13), régime_eaux char(12), z_min number(9,1), z_max number(9,1), id char(200)
Tester_gml
    TEST_CLAUSE = TEST $(FORMATS_LIST) CONTAINS gml
    TEST_DESCRIPTION = Test si parametre format contient gml
    BOOL_OP = OR
    TEST_MODE = Automatic
    PASSED -> Multiple_Test_Reprojection_GML [input 1]
    PASSED -> Multiple_Test_Reprojection_GML [input 2]
    PASSED -> Multiple_Test_Reprojection_GML [input 3]
    PASSED -> Multiple_Test_Reprojection_GML [input 4]
Multiple_Test_Reprojection_GML
    DEST = C:\Users\ndrissi\Downloads
    _COORDSYS = @Value(_coordsys)
    dest = exports
    Tester_shp_EPSG:3857_2_Passed_2 -> hydrographie.surface_eau (writer GML_2)
    Tester_shp_EPSG:3857_2_Passed -> hydrographie.surface_eau (writer GML_3)
    Tester_shp_EPSG:32631_2_Passed -> hydrographie.surface_eau (writer GML_4)
    Tester_EPSG:2154_2_Passed -> hydrographie.surface_eau (writer GML_1)
hydrographie.surface_eau (writer GML_1)
    attributes: source_geo xml_char(27), nature xml_char(13), régime_eaux xml_char(12), z_min xml_decimal(9,1), z_max xml_decimal(9,1), id xml_char(200)
hydrographie.surface_eau (writer GML_4)
    attributes: source_geo xml_char(27), nature xml_char(13), régime_eaux xml_char(12), z_min xml_decimal(9,1), z_max xml_decimal(9,1), id xml_char(200)
hydrographie.surface_eau (writer GML_3)
    attributes: source_geo xml_char(27), nature xml_char(13), régime_eaux xml_char(12), z_min xml_decimal(9,1), z_max xml_decimal(9,1), id xml_char(200)
hydrographie.surface_eau (writer GML_2)
    attributes: source_geo xml_char(27), nature xml_char(13), régime_eaux xml_char(12), z_min xml_decimal(9,1), z_max xml_decimal(9,1), id xml_char(200)
Tester_geotiff
    TEST_CLAUSE = TEST $(FORMATS_LIST) CONTAINS geotiff
    TEST_DESCRIPTION = Test si parametre format contient geojson
    BOOL_OP = OR
    TEST_MODE = Automatic
    PASSED -> AttributeCreator_3
Note: Assign colour to each feature
AttributeCreator_3
    ATTR_LIST = fme_color,1,1,1
    -> Multiple_Test_Reprojection_GEOTIFF [input 1]
    -> Multiple_Test_Reprojection_GEOTIFF [input 2]
    -> Multiple_Test_Reprojection_GEOTIFF [input 3]
    -> Multiple_Test_Reprojection_GEOTIFF [input 4]
Multiple_Test_Reprojection_GEOTIFF
    DEST = C:\Users\ndrissi\Downloads
    _COORDSYS = @Value(_coordsys)
    dest = exports
    Tester_shp_EPSG:32631_2_Passed -> ImageRasterizer_3
    Tester_shp_EPSG:3857_2_Passed -> ImageRasterizer_2
    Tester_EPSG:2154_2_Passed -> ImageRasterizer
    Tester_shp_EPSG:3857_2_Passed_2 -> ImageRasterizer_10
ImageRasterizer: Rasterizer
    BACKGROUND_VALUE = 0
    BACKGROUND_COLOR = 0.67451,0.67451,0.67451
    WIDTH = 1000
    HEIGHT = 1000
    RASTER -> hydrographie.surface_eau (writer GEOTIFF_1)
hydrographie.surface_eau (writer GEOTIFF_1)
    attributes: source_geo char(27), nature char(13), régime_eaux char(12), z_min decimal(9,1), z_max decimal(9,1), id char(200)
ImageRasterizer_3: Rasterizer
    GROUP_BY = fanout_attribute
    BACKGROUND_VALUE = 0
    BACKGROUND_COLOR = 0.674509803921569,0.674509803921569,0.674509803921569
    WIDTH = 1000
    HEIGHT = 1000
    RASTER -> hydrographie.surface_eau (writer GEOTIFF_2)
hydrographie.surface_eau (writer GEOTIFF_2)
    attributes: source_geo char(27), nature char(13), régime_eaux char(12), z_min decimal(9,1), z_max decimal(9,1), id char(200)
ImageRasterizer_2: Rasterizer
    BACKGROUND_VALUE = 0
    BACKGROUND_COLOR = 0.674509803921569,0.674509803921569,0.674509803921569
    WIDTH = 1000
    HEIGHT = 1000
    RASTER -> hydrographie.surface_eau (writer GEOTIFF_3)
hydrographie.surface_eau (writer GEOTIFF_3)
    attributes: source_geo char(27), nature char(13), régime_eaux char(12), z_min decimal(9,1), z_max decimal(9,1), id char(200)
ImageRasterizer_10: Rasterizer
    BACKGROUND_VALUE = 0
    BACKGROUND_COLOR = 0.674509803921569,0.674509803921569,0.674509803921569
    WIDTH = 1000
    HEIGHT = 1000
    RASTER -> hydrographie.surface_eau (writer GEOTIFF_4)
hydrographie.surface_eau (writer GEOTIFF_4)
    attributes: source_geo char(27), nature char(13), régime_eaux char(12), z_min decimal(9,1), z_max decimal(9,1), id char(200)
Tester_jpeg
    TEST_CLAUSE = TEST $(FORMATS_LIST) CONTAINS jpeg
    TEST_DESCRIPTION = Test si parametre format contient jpeg
    BOOL_OP = OR
    TEST_MODE = Automatic
    PASSED -> AttributeCreator_4
Note: Assign colour to each feature
AttributeCreator_4
    ATTR_LIST = fme_color,1,1,1
    -> Multiple_Test_Reprojection_JPEG [input 1]
    -> Multiple_Test_Reprojection_JPEG [input 2]
    -> Multiple_Test_Reprojection_JPEG [input 3]
    -> Multiple_Test_Reprojection_JPEG [input 4]
Multiple_Test_Reprojection_JPEG
    DEST = C:\Users\ndrissi\Downloads
    _COORDSYS = @Value(_coordsys)
    dest = exports
    Tester_EPSG:2154_2_Passed -> ImageRasterizer_4
    Tester_shp_EPSG:32631_2_Passed -> ImageRasterizer_6
    Tester_shp_EPSG:3857_2_Passed -> ImageRasterizer_5
    Tester_shp_EPSG:3857_2_Passed_2 -> ImageRasterizer_11
ImageRasterizer_4: Rasterizer
    BACKGROUND_VALUE = 0
    BACKGROUND_COLOR = 0.67451,0.67451,0.67451
    WIDTH = 1000
    HEIGHT = 1000
    RASTER -> hydrographie.surface_eau (writer JPEG_1)
hydrographie.surface_eau (writer JPEG_1)
    attributes: source_geo char(27), nature char(13), régime_eaux char(12), z_min decimal(9,1), z_max decimal(9,1), id char(200)
ImageRasterizer_6: Rasterizer
    GROUP_BY = fanout_attribute
    BACKGROUND_VALUE = 0
    BACKGROUND_COLOR = 0.674509803921569,0.674509803921569,0.674509803921569
    WIDTH = 1000
    HEIGHT = 1000
    RASTER -> hydrographie.surface_eau (writer JPEG_2)
hydrographie.surface_eau (writer JPEG_2)
    attributes: source_geo char(27), nature char(13), régime_eaux char(12), z_min decimal(9,1), z_max decimal(9,1), id char(200)
ImageRasterizer_5: Rasterizer
    BACKGROUND_VALUE = 0
    BACKGROUND_COLOR = 0.674509803921569,0.674509803921569,0.674509803921569
    WIDTH = 1000
    HEIGHT = 1000
    RASTER -> hydrographie.surface_eau (writer JPEG_3)
hydrographie.surface_eau (writer JPEG_3)
    attributes: source_geo char(27), nature char(13), régime_eaux char(12), z_min decimal(9,1), z_max decimal(9,1), id char(200)
ImageRasterizer_11: Rasterizer
    BACKGROUND_VALUE = 0
    BACKGROUND_COLOR = 0.674509803921569,0.674509803921569,0.674509803921569
    WIDTH = 1000
    HEIGHT = 1000
    RASTER -> hydrographie.surface_eau (writer JPEG_4)
hydrographie.surface_eau (writer JPEG_4)
    attributes: source_geo char(27), nature char(13), régime_eaux char(12), z_min decimal(9,1), z_max decimal(9,1), id char(200)
Tester_png
    TEST_CLAUSE = TEST $(FORMATS_LIST) CONTAINS png
    TEST_DESCRIPTION = Test si parametre format contient png
    BOOL_OP = OR
    TEST_MODE = Automatic
    PASSED -> AttributeCreator_5
Note: Assign colour to each feature
AttributeCreator_5
    ATTR_LIST = fme_color,1,1,1
    -> Multiple_Test_Reprojection_PNG [input 1]
    -> Multiple_Test_Reprojection_PNG [input 2]
    -> Multiple_Test_Reprojection_PNG [input 3]
    -> Multiple_Test_Reprojection_PNG [input 4]
Multiple_Test_Reprojection_PNG
    DEST = C:\Users\ndrissi\Downloads
    _COORDSYS = @Value(_coordsys)
    dest = exports
    Tester_EPSG:2154_2_Passed -> ImageRasterizer_7
    Tester_shp_EPSG:32631_2_Passed -> ImageRasterizer_9
    Tester_shp_EPSG:3857_2_Passed -> ImageRasterizer_8
    Tester_shp_EPSG:3857_2_Passed_2 -> ImageRasterizer_12
ImageRasterizer_7: Rasterizer
    BACKGROUND_VALUE = 0
    BACKGROUND_COLOR = 0.67451,0.67451,0.67451
    WIDTH = 1000
    HEIGHT = 1000
    RASTER -> hydrographie.surface_eau (writer PNGRASTER_1)
hydrographie.surface_eau (writer PNGRASTER_1)
    attributes: source_geo char(27), nature char(13), régime_eaux char(12), z_min decimal(9,1), z_max decimal(9,1), id char(200)
ImageRasterizer_9: Rasterizer
    GROUP_BY = fanout_attribute
    BACKGROUND_VALUE = 0
    BACKGROUND_COLOR = 0.674509803921569,0.674509803921569,0.674509803921569
    WIDTH = 1000
    HEIGHT = 1000
    RASTER -> hydrographie.surface_eau (writer PNGRASTER_2)
hydrographie.surface_eau (writer PNGRASTER_2)
    attributes: source_geo char(27), nature char(13), régime_eaux char(12), z_min decimal(9,1), z_max decimal(9,1), id char(200)
ImageRasterizer_8: Rasterizer
    BACKGROUND_VALUE = 0
    BACKGROUND_COLOR = 0.674509803921569,0.674509803921569,0.674509803921569
    WIDTH = 1000
    HEIGHT = 1000
    RASTER -> hydrographie.surface_eau (writer PNGRASTER_3)
hydrographie.surface_eau (writer PNGRASTER_3)
    attributes: source_geo char(27), nature char(13), régime_eaux char(12), z_min decimal(9,1), z_max decimal(9,1), id char(200)
ImageRasterizer_12: Rasterizer
    BACKGROUND_VALUE = 0
    BACKGROUND_COLOR = 0.674509803921569,0.674509803921569,0.674509803921569
    WIDTH = 1000
    HEIGHT = 1000
    RASTER -> hydrographie.surface_eau (writer PNGRASTER_4)
hydrographie.surface_eau (writer PNGRASTER_4)
    attributes: source_geo char(27), nature char(13), régime_eaux char(12), z_min decimal(9,1), z_max decimal(9,1), id char(200)

FME custom transformer Multiple_Test_Reprojector

Parameters:
- DEST = C:\Users\ndrissi\Downloads
- SRS_LIST = 2154 32631   # Python Script

Tester_EPSG:2154_Input (input)
    -> Tester_EPSG:2154
Tester_EPSG:2154
    TEST_CLAUSE = TEST $(SRS_LIST) CONTAINS 2154
    TEST_DESCRIPTION = Test si parametre SRS contient 2154 (Lambert93)
    BOOL_OP = OR
    TEST_MODE = Automatic
    PASSED -> Reprojector_2154
Reprojector_2154
    DEST = EPSG:2154
    INTERPOLATION_TYPE_NAME = Nearest Neighbor
    SOURCE = Read from feature
    RASTER_CELL_SIZE = Preserve Cells
    REPROJECTED -> Reprojector_2154_Reprojected (output)
Reprojector_2154_Reprojected (output)
Tester_shp_EPSG:32631_Input (input)
    -> Tester_shp_EPSG:32631
Tester_shp_EPSG:32631
    TEST_CLAUSE = TEST $(SRS_LIST) CONTAINS 32631
    TEST_DESCRIPTION = Test si parametre SRS contient EPSG:32631 soit WGS84(UTM 31N) transformation en shp
    BOOL_OP = OR
    TEST_MODE = Automatic
    PASSED -> Reprojector_32631
Reprojector_32631
    DEST = EPSG:32631
    INTERPOLATION_TYPE_NAME = Nearest Neighbor
    SOURCE = Read from feature
    RASTER_CELL_SIZE = Preserve Cells
    REPROJECTED -> Reprojector_32631_Reprojected (output)
Reprojector_32631_Reprojected (output)
Tester_shp_EPSG:3857_Input (input)
    -> Tester_shp_EPSG:3857
Tester_shp_EPSG:3857
    TEST_CLAUSE = TEST $(SRS_LIST) CONTAINS 3857
    TEST_DESCRIPTION = Test si parametre SRS contient EPSG:3857 soit WGS84(UTM 31N) transformation en shp
    BOOL_OP = OR
    TEST_MODE = Automatic
    PASSED -> Reprojector_3857
Reprojector_3857
    DEST = EPSG:3857
    INTERPOLATION_TYPE_NAME = Nearest Neighbor
    SOURCE = Read from feature
    RASTER_CELL_SIZE = Preserve Cells
    REPROJECTED -> Reprojector_3857_Reprojected (output)
Reprojector_3857_Reprojected (output)
Tester_shp_EPSG:3857_Input_2 (input)
    -> Tester_shp_EPSG:4326
Tester_shp_EPSG:4326
    TEST_CLAUSE = TEST $(SRS_LIST) CONTAINS 4326
    TEST_DESCRIPTION = Test si parametre contient EPSG:4326
    BOOL_OP = OR
    TEST_MODE = Automatic
    PASSED -> Reprojector_4326
Reprojector_4326
    DEST = EPSG:4326
    INTERPOLATION_TYPE_NAME = Nearest Neighbor
    SOURCE = Read from feature
    RASTER_CELL_SIZE = Preserve Cells
    REPROJECTED -> Reprojector_3857_Reprojected_2 (output)
Reprojector_3857_Reprojected_2 (output)

FME custom transformer Multiple_Test_Reprojection

Parameters:
- DEST = C:\Users\ndrissi\Downloads
- dest = exports   # RÃ©pertoire de destination 
- _COORDSYS = @Value(_coordsys)   # Coordsys

Tester_EPSG:2154_2_Input (input)
    -> Tester_EPSG:2154_2
Tester_EPSG:2154_2
    TEST_CLAUSE = TEST @Value(_coordsys) CONTAINS 2154
    TEST_DESCRIPTION = Test si parametre SRS contient 2154 (Lambert93)
    BOOL_OP = OR
    TEST_MODE = Automatic
    PASSED -> Tester_EPSG:2154_2_Passed (output)
Tester_EPSG:2154_2_Passed (output)
Tester_shp_EPSG:32631_2_Input (input)
    -> Tester_shp_EPSG:32631
Tester_shp_EPSG:32631
    TEST_CLAUSE = TEST @Value(_coordsys) CONTAINS 32631
    TEST_DESCRIPTION = Test si parametre SRS contient EPSG:32631 soit WGS84(UTM 31N) transformation en shp
    BOOL_OP = OR
    TEST_MODE = Automatic
    PASSED -> Tester_shp_EPSG:32631_2_Passed (output)
Tester_shp_EPSG:32631_2_Passed (output)
Tester_shp_EPSG:3857_2_Input (input)
    -> Tester_shp_EPSG:3857
Tester_shp_EPSG:3857
    TEST_CLAUSE = TEST @Value(_coordsys) CONTAINS 3857
    TEST_DESCRIPTION = Test si parametre SRS contient EPSG:3857 soit WGS84(UTM 31N) transformation en shp
    BOOL_OP = OR
    TEST_MODE = Automatic
    PASSED -> Tester_shp_EPSG:3857_2_Passed (output)
Tester_shp_EPSG:3857_2_Passed (output)
Tester_shp_EPSG:3857_2_Input_2 (input)
    -> Tester_shp_EPSG:4326
Tester_shp_EPSG:4326
    TEST_CLAUSE = TEST @Value(_coordsys) CONTAINS 4326
    TEST_DESCRIPTION = Test si parametre SRS contient EPSG:4326
    BOOL_OP = OR
    TEST_MODE = Automatic
    PASSED -> Tester_shp_EPSG:3857_2_Passed_2 (output)
Tester_shp_EPSG:3857_2_Passed_2 (output)
